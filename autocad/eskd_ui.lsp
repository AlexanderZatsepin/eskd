;;; ESKD simple DCL UI for AutoCAD 2016-2018.
;;; Load after:
;;;   autocad/eskd_auth.lsp
;;;   autocad/eskd_project_drawing_crud.lsp
;;;   autocad/eskd_wire_endpoint_crud.lsp
;;;
;;; Command:
;;;   ESKD

(vl-load-com)

(defun eskd-ui-dcl-path (/ current)
  (setq current (findfile "eskd_ui.dcl"))
  (if current
    current
    (findfile "autocad/eskd_ui.dcl")
  )
)

(defun eskd-ui-open-url (url)
  (startapp "cmd.exe" (strcat "/c start \"\" \"" url "\""))
)

(defun eskd-ui-value (value)
  (if value value "")
)

(defun eskd-ui-project-name-value ()
  (eskd-ui-value *eskd-current-project-name*)
)

(defun eskd-ui-authenticated-p ()
  (and *eskd-server-url* *eskd-username* *eskd-token*)
)

(defun eskd-ui-fill-auth-status (/ color status width height)
  (if (eskd-ui-authenticated-p)
    (progn
      (setq color 3)
      (setq status (strcat "Вход выполнен: " *eskd-username*))
    )
    (progn
      (setq color 1)
      (setq status "Вход не выполнен")
    )
  )
  (set_tile "auth_status" status)
  (setq width (dimx_tile "auth_indicator"))
  (setq height (dimy_tile "auth_indicator"))
  (start_image "auth_indicator")
  (fill_image 0 0 width height color)
  (end_image)
)
(defun eskd-ui-ensure-project-cabinet-options ()
  (if (not *eskd-project-options*) (setq *eskd-project-options* '("-")))
  (if (not *eskd-cabinet-options*) (setq *eskd-cabinet-options* '("-")))
  (if (not *eskd-selected-project-index*) (setq *eskd-selected-project-index* 0))
  (if (not *eskd-selected-cabinet-index*) (setq *eskd-selected-cabinet-index* 0))
)

(defun eskd-ui-ensure-wire-options ()
  (if (not *eskd-wire-type-options*) (setq *eskd-wire-type-options* '("-")))
  (if (not *eskd-wire-color-options*) (setq *eskd-wire-color-options* '("-")))
  (if (not *eskd-selected-wire-type-index*) (setq *eskd-selected-wire-type-index* 0))
  (if (not *eskd-selected-wire-color-index*) (setq *eskd-selected-wire-color-index* 0))
)

(defun eskd-ui-ensure-check-lines ()
  (if (not *eskd-wire-check-lines*) (setq *eskd-wire-check-lines* '("-")))
)

(defun eskd-ui-fill-popup (key items selected-index)
  (start_list key)
  (foreach item items
    (add_list item)
  )
  (end_list)
  (set_tile key (itoa selected-index))
)
(defun eskd-ui-fill-context ()
  (eskd-ui-fill-auth-status)
  (eskd-ui-ensure-project-cabinet-options)
  (set_tile "project_id" (eskd-ui-value *eskd-current-project-id*))
  (set_tile "project_code" (eskd-ui-value *eskd-current-project-code*))
  (set_tile "project_name" (eskd-ui-project-name-value))
  (eskd-ui-fill-popup "project_select" *eskd-project-options* *eskd-selected-project-index*)
  (set_tile "cabinet_id" (eskd-ui-value *eskd-current-cabinet-id*))
  (eskd-ui-fill-popup "cabinet_select" *eskd-cabinet-options* *eskd-selected-cabinet-index*)
  (set_tile "cabinet_code" (eskd-ui-value *eskd-current-cabinet-code*))
  (set_tile "cabinet_name" (eskd-ui-value *eskd-current-cabinet-name*))
  (set_tile "cabinet_description" (eskd-ui-value *eskd-current-cabinet-description*))
  (eskd-ui-ensure-wire-options)
  (eskd-ui-fill-popup "wire_type" *eskd-wire-type-options* *eskd-selected-wire-type-index*)
  (eskd-ui-fill-popup "wire_color" *eskd-wire-color-options* *eskd-selected-wire-color-index*)
  (eskd-ui-ensure-check-lines)
  (eskd-ui-fill-popup "wire_check_result" *eskd-wire-check-lines* 0)
)

(defun eskd-ui-save-context (/ project-code wire-type-index wire-color-index project-index cabinet-index)
  (setq project-code (get_tile "project_code"))
  (eskd-set-current-project-code project-code)
  (setq *eskd-current-project-name* (get_tile "project_name"))
  (setq *eskd-current-cabinet-code* (get_tile "cabinet_code"))
  (setq *eskd-current-cabinet-name* (get_tile "cabinet_name"))
  (setq *eskd-current-cabinet-description* (get_tile "cabinet_description"))
  (setq project-index (atoi (get_tile "project_select")))
  (setq cabinet-index (atoi (get_tile "cabinet_select")))
  (setq *eskd-selected-project-index* project-index)
  (setq *eskd-selected-cabinet-index* cabinet-index)
  (setq wire-type-index (atoi (get_tile "wire_type")))
  (setq wire-color-index (atoi (get_tile "wire_color")))
  (setq *eskd-selected-wire-type-index* wire-type-index)
  (setq *eskd-selected-wire-color-index* wire-color-index)
)

(defun eskd-ui-run-action (action)
  (cond
    ((= action "login") (c:ESKD_LOGIN))
    ((= action "status") (c:ESKD_STATUS))
    ((= action "logout") (c:ESKD_LOGOUT))
    ((= action "context_save") (c:ESKD_CONTEXT_STATUS))
    ((= action "projects_load") (c:ESKD_PROJECTS_LOAD))
    ((= action "project_select_apply") (c:ESKD_PROJECT_SELECT))
    ((= action "project_find") (c:ESKD_PROJECT_FIND))
    ((= action "project_sync") (c:ESKD_PROJECT_SYNC))
    ((= action "cabinets_load") (c:ESKD_CABINETS_LOAD))
    ((= action "cabinet_select_apply") (c:ESKD_CABINET_SELECT))
    ((= action "cabinet_sync") (c:ESKD_CABINET_SYNC))
    ((= action "wire_sync") (c:ESKD_WIRE_SYNC))
    ((= action "wire_insert") (c:ESKD_WIRE_INSERT))
    ((= action "dict_load") (c:ESKD_WIRE_DICTIONARIES_LOAD))
    ((= action "wire_assign") (c:ESKD_WIRE_ASSIGN_TYPE_COLOR))
    ((= action "wire_link") (c:ESKD_WIRE_LINK_REF))
    ((= action "wire_clear") (c:ESKD_WIRE_CLEAR_REF))
    ((= action "wire_check") (c:ESKD_WIRE_CHECK))
    ((= action "cambrics_report")
      (if *eskd-server-url*
        (eskd-ui-open-url (strcat (eskd-trim-right-slash *eskd-server-url*) "/reports/cambrics/"))
        (princ "\nАдрес сервера ESKD не задан. Сначала выполните вход.")
      )
    )
    (T nil)
  )
)

(defun eskd-ui-show-dialog (/ dcl-path dcl-id action)
  (setq dcl-path (eskd-ui-dcl-path))
  (if (not dcl-path)
    (progn
      (princ "\nНе найден eskd_ui.dcl. Добавьте папку autocad в Support File Search Path или загружайте LISP из этой папки.")
      nil
    )
    (progn
      (setq dcl-id (load_dialog dcl-path))
      (if (not (new_dialog "eskd_main" dcl-id))
        (progn
          (unload_dialog dcl-id)
          (princ "\nНе удалось открыть окно ESKD.")
          nil
        )
        (progn
          (setq action nil)
          (eskd-ui-fill-context)

          (action_tile "login" "(setq action \"login\")(done_dialog 1)")
          (action_tile "status" "(setq action \"status\")(done_dialog 1)")
          (action_tile "logout" "(setq action \"logout\")(done_dialog 1)")
          (action_tile "context_save" "(eskd-ui-save-context)(setq action \"context_save\")(done_dialog 1)")
          (action_tile "projects_load" "(eskd-ui-save-context)(setq action \"projects_load\")(done_dialog 1)")
          (action_tile "project_select_apply" "(eskd-ui-save-context)(setq action \"project_select_apply\")(done_dialog 1)")
          (action_tile "project_find" "(eskd-ui-save-context)(setq action \"project_find\")(done_dialog 1)")
          (action_tile "project_sync" "(eskd-ui-save-context)(setq action \"project_sync\")(done_dialog 1)")
          (action_tile "cabinets_load" "(eskd-ui-save-context)(setq action \"cabinets_load\")(done_dialog 1)")
          (action_tile "cabinet_select_apply" "(eskd-ui-save-context)(setq action \"cabinet_select_apply\")(done_dialog 1)")
          (action_tile "cabinet_sync" "(eskd-ui-save-context)(setq action \"cabinet_sync\")(done_dialog 1)")
          (action_tile "wire_sync" "(eskd-ui-save-context)(setq action \"wire_sync\")(done_dialog 1)")
          (action_tile "wire_insert" "(eskd-ui-save-context)(setq action \"wire_insert\")(done_dialog 1)")
          (action_tile "dict_load" "(eskd-ui-save-context)(setq action \"dict_load\")(done_dialog 1)")
          (action_tile "wire_assign" "(eskd-ui-save-context)(setq action \"wire_assign\")(done_dialog 1)")
          (action_tile "wire_link" "(setq action \"wire_link\")(done_dialog 1)")
          (action_tile "wire_clear" "(setq action \"wire_clear\")(done_dialog 1)")
          (action_tile "wire_check" "(eskd-ui-save-context)(setq action \"wire_check\")(done_dialog 1)")
          (action_tile "cambrics_report" "(setq action \"cambrics_report\")(done_dialog 1)")
          (action_tile "close" "(setq action \"close\")(done_dialog 0)")

          (start_dialog)
          (unload_dialog dcl-id)
          action
        )
      )
    )
  )
)

(defun c:ESKD (/ action keep-open)
  (setq keep-open T)
  (while keep-open
    (setq action (eskd-ui-show-dialog))
    (if (or (not action) (= action "close"))
      (setq keep-open nil)
      (eskd-ui-run-action action)
    )
  )
  (princ)
)
(princ "\nИнтерфейс ESKD загружен. Команда: ESKD.")
(princ)
